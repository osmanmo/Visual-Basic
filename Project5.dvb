Attribute VB_Name = "ThisDrawing"
Attribute VB_Base = "0{149DD748-EA85-45A6-93C5-AC50D0260C98}"
Attribute VB_GlobalNameSpace = False
Attribute VB_Creatable = False
Attribute VB_PredeclaredId = True
Attribute VB_Exposed = True
Attribute VB_TemplateDerived = False
Attribute VB_Customizable = True
Dim remaining As Double
Dim perrun As Integer
Dim remainder As Double
Function modulo(x, y)
 modulo = (x / y - Int(x / y)) * y
 End Function





Function Imperial(dimension)
        feet = Int(dimension)
        inches = Round(12 * (dimension - feet))
        If inches = 12 Then
        feet = feet + 1
        inches = 0
        End If
        foot = CStr(feet)
        inch = CStr(inches)
        If inches = 0 Then
            inch = "0"
        End If
        If feet = 0 Then
            foot = ""
        End If
        Imperial = foot + "-" + inch

    End Function











Function rebar(length, Barlength, lap, runs, Size, Label)
        perrun = Int(length / (Barlength - lap))
        remaining = modulo(length, (Barlength - lap))

        If remaining <= lap + 1.5 Then
            perrun = perrun - 1
            remaining = Barlength - (lap - remaining)
        End If
        If perrun <= 0 Then
            quant = runs
            rebar = CStr(quant) + Size + " " + Imperial(length) + " " + Label + " " + CStr(runs) + " Runs"
        End If


        If perrun > 0 Then
            quant = perrun * runs
            s = CStr(quant) + Size + " " + Imperial(Barlength) + " " + Label + " " + CStr(runs) + " runs" + "&&&" + CStr(runs) + Size + " " + Imperial(remaining) + " lap " + CStr(CInt(12 * lap))
            rebar = Split(s, "&&&")
        End If
        End Function
        
        
   

Function quantity(length, Spacing, Size, description, location)
        quant = Int(length / Spacing) + 2
        If InStr(description, "-") = 0 Then
        If InStr(description, "MK") = 0 Then
        description = "MK" & description
        End If
        End If
        s = CStr(quant) + Size + " " + description + " " + location + "@" + CStr(CInt(12 * Spacing))
        quantity = s
    End Function



Function ArrayLen(arr As Variant) As Integer
    ArrayLen = UBound(arr) - LBound(arr) + 1
End Function

Attribute VB_Name = "UserForm1"
Attribute VB_Base = "0{FD86B271-A949-47C0-9721-E368ED4EC5D5}{06C654CB-1571-43DC-9877-B36945C8C6E1}"
Attribute VB_GlobalNameSpace = False
Attribute VB_Creatable = False
Attribute VB_PredeclaredId = True
Attribute VB_Exposed = False
Attribute VB_TemplateDerived = False
Attribute VB_Customizable = False
 'Dim quant As Integer
    'Dim perrun As Integer
    'Dim remaining As Double
    'Dim lap As Double
    'Dim s As String
    

Private Sub CommandButton1_Click()
Me.Hide




If TextBox1.text <> "" Then
Barlength = CDbl(TextBox1.text)
lap = CDbl(TextBox2.text)
runs = CInt(TextBox3.text)
Label1 = TextBox4.text
size1 = TextBox9.text

End If



If TextBox5.text <> "" Then

Spacing = CDbl(TextBox5.text)
size2 = TextBox6.text
description2 = TextBox7.text
Label2 = TextBox8.text
End If


If TextBox10.text <> "" Then

spacing3 = CDbl(TextBox10.text)
size3 = TextBox11.text
description3 = TextBox12.text
Label3 = TextBox13.text
End If





Dim Height As Double
Height = 6
Do While 1
p1 = ThisDrawing.Utility.GetPoint(, "Pick the First Point")
p2 = ThisDrawing.Utility.GetPoint(p1, "Pick the Second Point")
If p1(0) = p2(0) And p1(1) = p2(1) Then
Exit Do
End If

d = ((p1(0) - p2(0)) ^ 2 + (p1(1) - p2(1)) ^ 2) ^ 0.5
length = d / 12 - 0.333333333333333

p1(0) = (p1(0) + p2(0)) / 2
p1(1) = (p1(1) + p2(1)) / 2
p1 = ThisDrawing.Utility.GetPoint(, "Pick the Insertion Point for Text")


If TextBox1.text <> "" Then
s = ThisDrawing.rebar(length, Barlength, lap, runs, size1, Label1)
If IsArray(s) = False Then
    s1 = s
    ThisDrawing.ModelSpace.AddText s1, p1, Height
    p1(1) = p1(1) - Height * 1.5
End If

If IsArray(s) Then
s1 = s(0)
s2 = s(1)
ThisDrawing.ModelSpace.AddText s1, p1, Height
p1(1) = p1(1) - Height * 1.5

ThisDrawing.ModelSpace.AddText s2, p1, Height
p1(1) = p1(1) - Height * 1.5
End If

End If

If TextBox5.text <> "" Then
s = ThisDrawing.quantity(length, Spacing, size2, description2, Label2)
s3 = s
ThisDrawing.ModelSpace.AddText s, p1, Height
p1(1) = p1(1) - Height * 1.5
End If


If TextBox10.text <> "" Then
s = ThisDrawing.quantity(length, spacing3, size3, description3, Label3)
s3 = s
ThisDrawing.ModelSpace.AddText s, p1, Height
End If

p1 = ThisDrawing.Utility.GetPoint(, "pick first point")
p2 = ThisDrawing.Utility.GetPoint(p1, "pick first point")
p3 = ThisDrawing.Utility.GetPoint(p2, "pick first point")
Dim p4(0 To 8) As Double

For i = 0 To UBound(p1)
    p4(i) = p1(i)
    p4(i + 3) = p2(i)
    p4(i + 6) = p3(i)
Next i

LeaderType = acLineWithArrow
ThisDrawing.ModelSpace.AddLeader p4, Nothing, acLineWithArrow

Loop
End Sub


Private Sub UserForm_Click()

End Sub

Attribute VB_Name = "UserForm2"
Attribute VB_Base = "0{33CB1F1D-DBBE-474E-AEBB-9C624C56E969}{B0BF1650-237E-41BA-BD14-36A925ECFCC9}"
Attribute VB_GlobalNameSpace = False
Attribute VB_Creatable = False
Attribute VB_PredeclaredId = True
Attribute VB_Exposed = False
Attribute VB_TemplateDerived = False
Attribute VB_Customizable = False

Private Sub CommandButton1_Click()
 ' Create a reference to a new Excel application
 Dim execl As New Excel.Application
 execl.Visible = True

 ' Create a new workbook
 Dim workbk As Excel.Workbook
 Set workbk = execl.Workbooks.Add

 ' Get the first worksheet

 Dim worksht As Excel.Worksheet
 Set worksht = workbk.Worksheets(1)
 ' Add Intro Text to cell A1
 Dim workshtRange As Excel.Range
 Set workshtRange = worksht.Range("A1")
 workshtRange.Value = "Rebar Quantities as you may want them"

 ' Add column headers
 worksht.Range("B2").Value2 = "Quantity"
 worksht.Range("C2").Value2 = "Size"
 worksht.Range("D2").Value2 = "Length (ft)"
 ' Step through each of the objects in the current space
 ' and extract only the circles
 Dim ent As AcadEntity
 Dim text As AcadText

 Dim row As Integer
 row = 3

 For Each ent In ThisDrawing.ModelSpace
 If ent.ObjectName = "AcDbText" And ent.Layer = "Layer10" Then
 Set obj = ent
 tex = obj.TextString
 tex = Replace(tex, "#", " ")
 tex = Split(tex, " ")
 worksht.Range("B" & CInt(row)).Value2 = tex(0)
 worksht.Range("C" & CInt(row)).Value2 = "'" & tex(1)
 worksht.Range("D" & CInt(row)).Value2 = "'" & tex(2)
 
 row = row + 1
 End If
 Next ent
End Sub

Attribute VB_Name = "UserForm3"
Attribute VB_Base = "0{B3B833EA-08AE-4C67-8065-4B9EAFAC2509}{B2AD48DD-892A-4A40-82D0-FA8CD35E30E5}"
Attribute VB_GlobalNameSpace = False
Attribute VB_Creatable = False
Attribute VB_PredeclaredId = True
Attribute VB_Exposed = False
Attribute VB_TemplateDerived = False
Attribute VB_Customizable = False
Private Sub CommandButton1_Click()
Me.Hide




Barlength = CDbl(Barlength.text)
lap = CDbl(lap.text)
Spacing = CInt(Spacing.text)
Label = Label.text
Size = Size.text



Dim heights As Double
heights = 6



Do While 1
p1 = ThisDrawing.Utility.GetPoint(, "Pick the first point of longitudinal")
p2 = ThisDrawing.Utility.GetPoint(p1, "Pick the second point of longitudinal")
p3 = ThisDrawing.Utility.GetPoint(, "Pick the first point of Transverse")
p4 = ThisDrawing.Utility.GetPoint(p3, "Pick the second point of Transverse")
d1 = ((p1(0) - p2(0)) ^ 2 + (p1(1) - p2(1)) ^ 2) ^ 0.5
d2 = ((p3(0) - p4(0)) ^ 2 + (p3(1) - p4(1)) ^ 2) ^ 0.5
length1 = d1 / 12 - 0.3333333333333
length2 = d2 / 12
runs = (Round(length2 / Spacing) + 1)

p1 = ThisDrawing.Utility.GetPoint(, "Pick the Insertion Point for Text")
s = ThisDrawing.rebar(length1, Barlength, lap, runs, Size, Label)

If IsArray(s) = False Then
    s1 = s
    ThisDrawing.ModelSpace.AddText s1, p1, heights
    p1(1) = p1(1) - heights * 1.5
End If

If IsArray(s) Then
s1 = s(0)
s2 = s(1)
ThisDrawing.ModelSpace.AddText s1, p1, heights
p1(1) = p1(1) - heights * 1.5

ThisDrawing.ModelSpace.AddText s2, p1, heights
p1(1) = p1(1) - heights * 1.5
End If

p1 = ThisDrawing.Utility.GetPoint(, "pick first point")
p2 = ThisDrawing.Utility.GetPoint(p1, "pick first point")
p3 = ThisDrawing.Utility.GetPoint(p2, "pick first point")
Dim p9(0 To 8) As Double

For i = 0 To UBound(p1)
    p9(i) = p1(i)
    p9(i + 3) = p2(i)
    p9(i + 6) = p3(i)
Next i

LeaderType = acLineWithArrow
ThisDrawing.ModelSpace.AddLeader p9, Nothing, acLineWithArrow




Loop



End Sub

Attribute VB_Name = "UserForm4"
Attribute VB_Base = "0{C35BDE79-4657-4C6F-B835-5D66620DE011}{BCB7889B-E091-47B7-89F4-F20E9CBE56FF}"
Attribute VB_GlobalNameSpace = False
Attribute VB_Creatable = False
Attribute VB_PredeclaredId = True
Attribute VB_Exposed = False
Attribute VB_TemplateDerived = False
Attribute VB_Customizable = False
Private Sub CommandButton1_Click()
Me.Hide




Barlength = CDbl(TextBox1.text)
lap = CDbl(TextBox2.text)
Spacing = CInt(TextBox3.text)
Label = TextBox5.text
Size = TextBox4.text



Dim heights As Double
heights = 12



Do While 1
p1 = ThisDrawing.Utility.GetPoint(, "Pick the first point of longitudinal")
p2 = ThisDrawing.Utility.GetPoint(p1, "Pick the second point of longitudinal")

d1 = ((p1(0) - p2(0)) ^ 2 + (p1(1) - p2(1)) ^ 2) ^ 0.5

length1 = d1 / 12

runs = ThisDrawing.Utility.GetInteger("How many Runs")

p1 = ThisDrawing.Utility.GetPoint(, "Pick the Insertion Point for Text")
s = ThisDrawing.rebar(length1, Barlength, lap, runs, Size, Label)

If IsArray(s) = False Then
    s1 = s
    ThisDrawing.ModelSpace.AddText s1, p1, heights
    p1(1) = p1(1) - heights * 1.5
End If

If IsArray(s) Then
s1 = s(0)
s2 = s(1)
ThisDrawing.ModelSpace.AddText s1, p1, heights
p1(1) = p1(1) - heights * 1.5

ThisDrawing.ModelSpace.AddText s2, p1, heights
p1(1) = p1(1) - heights * 1.5
End If

p1 = ThisDrawing.Utility.GetPoint(, "pick first point")
p2 = ThisDrawing.Utility.GetPoint(p1, "pick first point")
p3 = ThisDrawing.Utility.GetPoint(p2, "pick first point")
Dim p9(0 To 8) As Double

For i = 0 To UBound(p1)
    p9(i) = p1(i)
    p9(i + 3) = p2(i)
    p9(i + 6) = p3(i)
Next i

LeaderType = acLineWithArrow
ThisDrawing.ModelSpace.AddLeader p9, Nothing, acLineWithArrow




Loop



End Sub
